UNPREDICTABLE-GR-MIB DEFINITIONS ::= BEGIN

IMPORTS
	enterprises,
	MODULE-IDENTITY,
	OBJECT-TYPE,
	Unsigned32
		FROM SNMPv2-SMI
	DisplayString
		FROM SNMPv2-TC
	OBJECT-GROUP,
	MODULE-COMPLIANCE
		FROM SNMPv2-CONF;

unpredictableMIB MODULE-IDENTITY
	LAST-UPDATED "201702011456Z"	-- Feb 1, 2017 2:56:00 PM
	ORGANIZATION "Uminho"
	CONTACT-INFO
		"jfp88@gmail.com"
	DESCRIPTION
		"this mib contain two objects, unpredictableParm and unpredictableTable.
		the first one contains the parameters used to create the second one.
		the second one is a table containing, in each entry, a random number."
	REVISION "201702011456Z"	-- Feb 1, 2017 2:56:00 PM
	DESCRIPTION
		"Initial version."
	-- 1.3.6.1.4.1.3333 --
	-- 1.3.6.1.4.1.3333
	::= { enterprises 3333 }


-- Scalars and Tables --
unpredictableObjects OBJECT IDENTIFIER 
	-- 1.3.6.1.4.1.3333.1 --
	-- 1.3.6.1.4.1.3333.1
	::= { unpredictableMIB 1 }

unpredictableParam OBJECT IDENTIFIER 
	-- 1.3.6.1.4.1.3333.1.1 --
	-- 1.3.6.1.4.1.3333.1.1
	::= { unpredictableObjects 1 }

unpredictableN OBJECT-TYPE
	SYNTAX  Unsigned32
	MAX-ACCESS read-only
	STATUS  current
	DESCRIPTION
		"Number of lines in the unpredictableTable"
	-- 1.3.6.1.4.1.3333.1.1.1 --
	-- 1.3.6.1.4.1.3333.1.1.1
	::= { unpredictableParam 1 }


unpredictableR OBJECT-TYPE
	SYNTAX  Unsigned32
	MAX-ACCESS read-only
	STATUS  current
	DESCRIPTION
		"Refresh rate, per second, of unpredictableTable"
	-- 1.3.6.1.4.1.3333.1.1.2 --
	-- 1.3.6.1.4.1.3333.1.1.2
	::= { unpredictableParam 2 }


unpredictableD OBJECT-TYPE
	SYNTAX  Unsigned32
	MAX-ACCESS read-only
	STATUS  current
	DESCRIPTION
		"Number of digits that each random number in unpredictableTable has"
	-- 1.3.6.1.4.1.3333.1.1.3 --
	-- 1.3.6.1.4.1.3333.1.1.3
	::= { unpredictableParam 3 }


unpredictableRCmd OBJECT-TYPE
	SYNTAX  OCTET STRING (SIZE (0..255))
	MAX-ACCESS read-write
	STATUS  current
	DESCRIPTION
		"Defines the authorization command for the reset operation."
	-- 1.3.6.1.4.1.3333.1.1.4 --
	-- 1.3.6.1.4.1.3333.1.1.4
	::= { unpredictableParam 4 }


unpredictableTable OBJECT-TYPE
	SYNTAX  SEQUENCE OF UnpredictableEntry
	MAX-ACCESS not-accessible
	STATUS  current
	DESCRIPTION
		"This table is constructed with the parameters found in unpredictableParam and contains one random number per entry"
	-- 1.3.6.1.4.1.3333.1.2 --
	-- 1.3.6.1.4.1.3333.1.2
	::= { unpredictableObjects 2 }


unpredictableEntry OBJECT-TYPE
	SYNTAX  UnpredictableEntry
	MAX-ACCESS not-accessible
	STATUS  current
	DESCRIPTION
		"random number"
	INDEX {
		rndIndex }
	-- 1.3.6.1.4.1.3333.1.2.1 --
	-- 1.3.6.1.4.1.3333.1.2.1
	::= { unpredictableTable 1 }


UnpredictableEntry ::= SEQUENCE {

	rndIndex  Unsigned32,
	rndNumber DisplayString }


rndIndex OBJECT-TYPE
	SYNTAX  Unsigned32
	MAX-ACCESS not-accessible
	STATUS  current
	DESCRIPTION
		"The index for each table entry"
	-- 1.3.6.1.4.1.3333.1.2.1.1 --
	-- 1.3.6.1.4.1.3333.1.2.1.1
	::= { unpredictableEntry 1 }


rndNumber OBJECT-TYPE
	SYNTAX  DisplayString (SIZE (0..255))
	MAX-ACCESS read-only
	STATUS  current
	DESCRIPTION
		"The random number"
	-- 1.3.6.1.4.1.3333.1.2.1.2 --
	-- 1.3.6.1.4.1.3333.1.2.1.2
	::= { unpredictableEntry 2 }


-- Conformance --
unpredictableConf OBJECT IDENTIFIER 
	-- 1.3.6.1.4.1.3333.3 --
	-- 1.3.6.1.4.1.3333.2
	::= { unpredictableMIB 2 }

-- Groups --
unpredictableGroups OBJECT IDENTIFIER 
	-- 1.3.6.1.4.1.3333.3.1 --
	-- 1.3.6.1.4.1.3333.2.1
	::= { unpredictableConf 1 }

-- Compliances --
unpredictableCompliances OBJECT IDENTIFIER 
	-- 1.3.6.1.4.1.3333.3.2 --
	-- 1.3.6.1.4.1.3333.2.2
	::= { unpredictableConf 2 }

unpredictableParmGroup OBJECT-GROUP
	OBJECTS {
		unpredictableN,
		unpredictableR,
		unpredictableD,
		unpredictableRCmd }
	STATUS  current
	DESCRIPTION
		"Parms objects."
	-- 1.3.6.1.4.1.3333.3.1.1 --
	-- 1.3.6.1.4.1.3333.2.1.1
	::= { unpredictableGroups 1 }

unpredictableTableGroup OBJECT-GROUP
	OBJECTS {
		rndNumber }
	STATUS  current
	DESCRIPTION
		"Table Objects"
	-- 1.3.6.1.4.1.3333.3.1.2 --
	-- 1.3.6.1.4.1.3333.2.1.2
	::= { unpredictableGroups 2 }


unpredictableCompliance MODULE-COMPLIANCE
	STATUS  current
	DESCRIPTION
		"The compliance statement for SNMP entities that implement this MIB."

	MODULE UNPREDICTABLE-GR-MIB
	MANDATORY-GROUPS {
			unpredictableParmGroup,
			unpredictableTableGroup }

	-- 1.3.6.1.4.1.3333.3.2.1 --
	-- 1.3.6.1.4.1.3333.2.2.1
	::= { unpredictableCompliances 1 }

END
